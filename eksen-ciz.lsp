;| EKSEN
Çember veya yay'a dikey ve yatay eksenleri çizer
Kullanıcı, nesne seçimi veya merkez noktası belirleme ile eksen çizebilir.
Çıkıntı mesafesi ayarlanabilir.
Son işlem geri alınabilir.

12/12/2024 - İlk sürüm
11/06/2025 - Son güncelleme

R15

Mesut Akcan
makcan@gmail.com

https://www.youtube.com/mesutakcan
https://mesutakcan.blogspot.com
|;

(vl-load-com)
(setq cikinti 3) ; Çıkıntı mesafesi

(defun c:EKSEN (/ cikis doc edata eksenSayisi ent menuSecimi menuTxt n ss yeniCikinti) 
  (setq
    doc (vla-get-activedocument (vlax-get-acad-object)) ; aktif çizim
    undoMark nil ; Geri alma işareti
  )
  ; Çalışma sırasında hata olursa
  (defun *error* (msg)
    (if undoMark (vla-endundomark doc)) ; UndoMark başlatıldıysa bitir
    (if (and msg (/= msg "Function cancelled"))
      (princ (strcat "\nHata: " msg))
    )
    (princ)
  ) 

  ; Eksen katmanı yoksa ekle
  (KatmanEkle "EKSEN" "CENTER" 4) ; Katman adı, çizgi tipi ve çizgi rengi
  (setq eksenSayisi 0) ; Eksen sayısı
  
  ; Çıkış seçilene kadar sonsuz döngü
  (while T 
    ; Seçenekler:
		; -----------
    ; 1-Merkez noktası tıkla
    ; 2-Çıkıntı ayarla
    ; 3-Geri al
		; 4-Nesne seç (Varsayılan seçenek)
    (prompt (strcat "\nÇıkıntı:" (rtos cikinti))) ; Çıkıntı mesafesi
    (initget "Nesne Çıkıntı Geri") ; Menü elemanları
    (setq menuTxt (strcat "[Nesne seç/Çıkıntı" (if (> eksenSayisi 0) "/Geri al" "") "]"))
    (setq menuSecimi ; Menü seçimi
          (getpoint (strcat "\nMerkez noktası belirle " menuTxt " <Nesne seç>: "))
    )

    (cond 
      ;1-Merkez noktası tıklandı ise
      ;-----------------------------
      ((= 'LIST (type menuSecimi)) ; Dönen değer liste ise
       (EksenCiz menuSecimi (getdist menuSecimi "\nEksen yarıçapı:") cikinti doc)
       (setq eksenSayisi (1+ eksenSayisi))
      )

      ;2-"Çıkıntı" seçildi ise
			;------------------------------
      ((= menuSecimi "Çıkıntı") ; Dönen değer "Çıkıntı" ise
        ; Çıkıntı mesafesini ayarla
        (setq yeniCikinti (getdist (strcat "\nÇıkıntı mesafesi <" (rtos cikinti) ">: ")))
        (if yeniCikinti (setq cikinti yeniCikinti))
      )

      ;3-"Geri al" seçildi ise
      ; ----------------------
      ((= menuSecimi "Geri")
       (progn
         (repeat 2 (entdel (entlast))); Son iki çizgiyi sil
         (setq eksenSayisi (1- eksenSayisi)); Eksen sayısını azalt
       )
      )

      ;4-"Nesne seç" seçildi veya Enter'e basıldı ise
      ;---------------------------------------------
      (T
       (if (setq ss (ssget '((0 . "CIRCLE,ARC"))))  ; Yay veya çember seç
         ;seçim yapıldıysa
         ;----------------
         (progn 
           (repeat (setq n (sslength ss))  ; Seçili nesne sayısı kadar döngü
             (setq ent (ssname ss (setq n (1- n))) ; seçim listesindeki varlık adı
                   edata (entget ent) ; Varlık verileri. DXF bilgiler
             )
             (EksenCiz (trans (cdr (assoc 10 edata)) ent 1) (cdr (assoc 40 edata)) cikinti doc)
             (setq eksenSayisi (1+ eksenSayisi))
           );repeat
         );progn

         ;seçim yapılmadıysa
         ;------------------
         (prompt "\n*Çember veya yay seçilmedi!*")
       );if
      );T
    );cond
  );while
  (princ)
);defun

; Eksen çiz
; ---------
; Çember veya yay'a dikey ve yatay eksenleri çizer
; mn: Merkez noktası
; r: Yarıçap
; c: Çıkıntı mesafesi
; d: Aktif belge
(defun EksenCiz (mn r c d)  ; Merkez nokta, yarıçap, çıkıntı, doc
  (vla-startundomark d)
  (setq
    r (+ r c) ; Çıkıntıyı yarıçapa ekle
    undoMark T ; UndoMark başlatıldı
  )
  ; Dikey ve yatay eksenleri çiz
  ;-----------------------------
  ; 0 ve 90 derece açıları için döngü
  (foreach aci (list 0 (/ pi 2))
    (entmake 
      (list 
        (cons 0 "LINE") ; Nesne tipi
        (cons 8 "EKSEN") ; Katman
        (cons 10 (trans (polar mn aci r) 1 0)) ; Başlangıç noktası
        (cons 11 (trans (polar mn (+ pi aci) r) 1 0)) ; Bitiş noktası
      );list
    );entmake
  );foreach
	(vla-endundomark d)
  (setq undoMark nil)
);defun

; Katman Ekle
; -----------
; Belirtilen ad, çizgi tipi ve çizgi rengi ile yeni bir katman oluşturur.
; katmanAdi - Oluşturulacak katmanın adı.
; cizgiTipi - Katmana atanacak çizgi tipi.
; cizgiRengi - Katmana atanacak renk.  
(defun KatmanEkle (katmanAdi cizgiTipi cizgiRengi) 
  ; Çizgi tipini kontrol et
  (if (not (tblsearch "LTYPE" cizgiTipi))  ; Çizgi tipi yoksa
    (progn 
      (command "-linetype" "load" cizgiTipi "acadiso.lin" "") ; Çizgi tipini yükle
      (if (not (tblsearch "LTYPE" cizgiTipi)) ; Çizgi tipi yüklenemediyse
        (princ (strcat "\n" cizgiTipi " çizgi tipi yüklenemedi."))
      );if
    );progn
  );if
  
  ; Katmanı kontrol et
  (if (not (tblsearch "LAYER" katmanAdi))  ; Katman yoksa
    (entmake  ; Katman yap
      (list 
        (cons 0 "LAYER") ; Katman
        (cons 100 "AcDbSymbolTableRecord")
        (cons 100 "AcDbLayerTableRecord")
        (cons 70 0) ; Katman durumu ON
        (cons 2 katmanAdi) ; Katman adı
        (cons 6 cizgiTipi) ; Çizgi tipi
        (cons 62 cizgiRengi) ; Çizgi rengi
        (cons 370 -3) ; Çizgi kalınlığı. Default
      );list
    );entmake
  );if
);defun

(princ "\nUygulama yüklendi. Komut: EKSEN")
(princ)
;--
